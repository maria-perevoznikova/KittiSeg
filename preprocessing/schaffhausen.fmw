FME workspace schaffhausen.fmw

Parameters:
- DestDataset_PNGRASTER_9 = C:\Projects\VP2\MLdata\gt_tiles   # Destination PNG (Portable Network Graphics) Folder
- DestDataset_PNGRASTER_7 = C:\Projects\VP2\MLdata\gt_tiles\1   # Destination PNG (Portable Network Graphics) Folder
- DestDataset_PNGRASTER_6 = C:\Projects\VP2\MLdata\orthos_tiles   # Destination PNG (Portable Network Graphics) Folder
- DestDataset_PNGRASTER = C:\Projects\VP2\MLdata\orthos_tiles\1   # Destination PNG (Portable Network Graphics) Folder
- SourceDataset_TIFF_7 = ""C:\Projects\VP2\MLdata\_orthos\*.tif" "C:\Projects\VP2\MLdata\_orthos\*.tiff" "C:\Projects\VP2\MLdata\_orthos\*.itiff" "C:\Projects\VP2\MLdata\_orthos\*.ovr""   # Source TIFF (Tagged Image File Format) File(s)
- DestDataset_PNGRASTER_8 = C:\Projects\VP2\MLdata\_orthos_3bands   # Destination PNG (Portable Network Graphics) Folder
- SourceDataset_TIFF_6 = ""C:\Projects\VP2\MLdata\_gt1\*.tif" "C:\Projects\VP2\MLdata\_gt1\*.tiff" "C:\Projects\VP2\MLdata\_gt1\*.itiff" "C:\Projects\VP2\MLdata\_gt1\*.ovr""   # Source TIFF (Tagged Image File Format) File(s)
- SourceDataset_PNGRASTER = C:\Projects\VP2\MLdata\_orthos_3bands\*.png   # Source PNG (Portable Network Graphics) File(s)
- SourceDataset_PNGRASTER_2 = C:\Projects\VP2\MLdata\_gt1_color\*.png   # Source PNG (Portable Network Graphics) File(s)

Readers:
- TIFF_1: TIFF from $(SourceDataset_TIFF_7)
- TIFF_2: TIFF from $(SourceDataset_TIFF_6)
- PNGRASTER_1: PNGRASTER from $(SourceDataset_PNGRASTER)
- PNGRASTER_2: PNGRASTER from $(SourceDataset_PNGRASTER_2)

Writers:
- PNGRASTER_3: PNGRASTER to $(DestDataset_PNGRASTER_9)
- PNGRASTER_4: PNGRASTER to $(DestDataset_PNGRASTER_7)
- PNGRASTER_5: PNGRASTER to $(DestDataset_PNGRASTER_6)
- PNGRASTER_6: PNGRASTER to $(DestDataset_PNGRASTER)
- PNGRASTER_7: PNGRASTER to $(DestDataset_PNGRASTER_8)

Note: GT_palette
TIFF (reader TIFF_2) [off]
    -> RasterProperties_4
RasterProperties_4: RasterPropertyExtractor
    -> RasterInterpretationCoercer
RasterInterpretationCoercer
    INTERPRETATION = UInt8
    FLOAT_TO_INTEGER = Round
    COLOR_TO_NUMERIC = Bounded cast
    NUMERIC_TO_NUMERIC = Bounded cast
    -> AttributeFileReader_2
AttributeFileReader_2
    FILE_NAME = C:\Projects\VP2\MLdata\palette1.txt
    DEST_ATTR = _palette
    CHAR_ENCODING = utf-8
    -> RasterPaletteAdder_2
RasterPaletteAdder_2
    PALETTE_ATTR = _palette
    -> Raster100 (writer PNGRASTER_3)
Raster100 (writer PNGRASTER_3)
Note: Remove band
TIFF (reader TIFF_1) [off]
    -> RasterProperties_3
RasterProperties_3: RasterPropertyExtractor
    -> RasterSelector_2
RasterSelector_2
    SELECTION_MODE = Band and Palette List
    BAND_LIST = 2
    -> RasterBandRemover_2
RasterBandRemover_2
    -> RasterInterpretationCoercer_2
RasterInterpretationCoercer_2
    INTERPRETATION = RGB24
    COLOR_TO_COLOR = Scale by data type
    RGBA_TO_RGB = Drop the alpha band
    FLOAT_TO_INTEGER = Round
    NUMERIC_TO_COLOR = Scale by data values
    -> TIFF (writer PNGRASTER_7)
TIFF (writer PNGRASTER_7)
Note: OrthoPhotos
PNGRASTER (reader PNGRASTER_1)
    attributes: nodata_values char(255)
    -> RasterProperties
RasterProperties: RasterPropertyExtractor
    -> ClipSize
ClipSize: AttributeCreator
    ATTR_LIST = _tile_num_rows,512,_tile_num_columns,512,_clip_rows,@Evaluate(@Value(_num_rows)-@Value(_num_rows)%512),_clip_columns,@Evaluate(@Value(_num_columns)-@Value(_num_columns)%512)
    -> RasterClipper
    -> RasterClipper_4 [off]
RasterClipper: RasterSubsetter
    START_ROW = 0
    NUM_TOP_PADDING_ROWS = 0
    START_COLUMN = 0
    NUM_LEFT_PADDDING_COLUMNS = 0
    NUM_BOTTOM_PADDING_ROWS = 0
    NUM_RIGHT_PADDDING_COLUMNS = 0
    NUM_COLUMNS = @Value(_clip_columns)
    NUM_ROWS = @Value(_clip_rows)
    -> RasterTiler
RasterTiler
    TILE_ROW_ATTRIBUTE = _tile_row
    TILESIZE_OR_NUMTILES = Tile Size
    SEED_ROW = 0
    NUM_TILE_ROWS = @Value(_tile_num_rows)
    TILE_COLUMN_ATTRIBUTE = _tile_column
    NUM_TILE_COLUMNS = @Value(_tile_num_columns)
    FORCE_EQUAL_SIZED_TILES = No
    NUM_VERTICAL_TILES_ATTRIBUTE = _num_tile_rows
    SEED_COLUMN = 0
    RASTER_INDEX_ATTRIBUTE = _raster_index
    NUM_HORIZONTAL_TILES_ATTRIBUTE = _num_tile_columns
    TILES -> TileName
TileName: StringConcatenator
    ACTION = Create New Attribute
    VAL_ATTR = _tile_name
    PARM_LINE = @Value(fme_basename)_@Value(_tile_column)_@Value(_tile_row)
    -> TIFF (writer PNGRASTER_5)
TIFF (writer PNGRASTER_5)
Note: Clip with shift
RasterClipper_4: RasterSubsetter
    START_ROW = @Value(_tile_num_rows)/2
    NUM_TOP_PADDING_ROWS = 0
    START_COLUMN = "@Value(_tile_num_columns)/2 "
    NUM_LEFT_PADDDING_COLUMNS = 0
    NUM_BOTTOM_PADDING_ROWS = 0
    NUM_RIGHT_PADDDING_COLUMNS = 0
    NUM_COLUMNS = @Value(_clip_columns)
    NUM_ROWS = @Value(_clip_rows)
    -> RasterTiler_4
RasterTiler_4
    TILE_ROW_ATTRIBUTE = _tile_row
    TILESIZE_OR_NUMTILES = Tile Size
    SEED_ROW = 0
    NUM_TILE_ROWS = @Value(_tile_num_rows)
    TILE_COLUMN_ATTRIBUTE = _tile_column
    NUM_TILE_COLUMNS = @Value(_tile_num_columns)
    FORCE_EQUAL_SIZED_TILES = No
    NUM_VERTICAL_TILES_ATTRIBUTE = _num_tile_rows
    SEED_COLUMN = 0
    RASTER_INDEX_ATTRIBUTE = _raster_index
    NUM_HORIZONTAL_TILES_ATTRIBUTE = _num_tile_columns
    TILES -> TileName_4
TileName_4: StringConcatenator
    ACTION = Create New Attribute
    VAL_ATTR = _tile_name
    PARM_LINE = @Value(fme_basename)_@Value(_tile_column)_@Value(_tile_row)
    -> TIFF (writer PNGRASTER_6)
TIFF (writer PNGRASTER_6)
Note: GroundTruth
PNGRASTER (reader PNGRASTER_2)
    -> RasterProperties_2
RasterProperties_2: RasterPropertyExtractor
    -> ClipSize_2
ClipSize_2: AttributeCreator
    ATTR_LIST = _tile_num_rows,512,_tile_num_columns,512,_clip_rows,@Evaluate(@Value(_num_rows)-@Value(_num_rows)%512),_clip_columns,@Evaluate(@Value(_num_columns)-@Value(_num_columns)%512)
    -> RasterClipper_2
    -> RasterClipper_3 [off]
RasterClipper_2: RasterSubsetter
    START_ROW = 0
    NUM_TOP_PADDING_ROWS = 0
    START_COLUMN = 0
    NUM_LEFT_PADDDING_COLUMNS = 0
    NUM_BOTTOM_PADDING_ROWS = 0
    NUM_RIGHT_PADDDING_COLUMNS = 0
    NUM_COLUMNS = @Value(_clip_columns)
    NUM_ROWS = @Value(_clip_rows)
    -> RasterTiler_2
RasterTiler_2
    TILE_ROW_ATTRIBUTE = _tile_row
    TILESIZE_OR_NUMTILES = Tile Size
    SEED_ROW = 0
    NUM_TILE_ROWS = @Value(_tile_num_rows)
    TILE_COLUMN_ATTRIBUTE = _tile_column
    NUM_TILE_COLUMNS = @Value(_tile_num_columns)
    FORCE_EQUAL_SIZED_TILES = No
    NUM_VERTICAL_TILES_ATTRIBUTE = _num_tile_rows
    SEED_COLUMN = 0
    RASTER_INDEX_ATTRIBUTE = _raster_index
    NUM_HORIZONTAL_TILES_ATTRIBUTE = _num_tile_columns
    TILES -> TileName_2
TileName_2: StringConcatenator
    ACTION = Create New Attribute
    VAL_ATTR = _tile_name
    PARM_LINE = @Value(fme_basename)_@Value(_tile_column)_@Value(_tile_row)
    -> Raster1 (writer PNGRASTER_3)
Raster1 (writer PNGRASTER_3)
Note: Clip with shift
RasterClipper_3: RasterSubsetter
    START_ROW = @Value(_tile_num_rows)/2
    NUM_TOP_PADDING_ROWS = 0
    START_COLUMN = @Value(_tile_num_columns)/2
    NUM_LEFT_PADDDING_COLUMNS = 0
    NUM_BOTTOM_PADDING_ROWS = 0
    NUM_RIGHT_PADDDING_COLUMNS = 0
    NUM_COLUMNS = @Value(_clip_columns)
    NUM_ROWS = @Value(_clip_rows)
    -> RasterTiler_3
RasterTiler_3
    TILE_ROW_ATTRIBUTE = _tile_row
    TILESIZE_OR_NUMTILES = Tile Size
    SEED_ROW = 0
    NUM_TILE_ROWS = @Value(_tile_num_rows)
    TILE_COLUMN_ATTRIBUTE = _tile_column
    NUM_TILE_COLUMNS = @Value(_tile_num_columns)
    FORCE_EQUAL_SIZED_TILES = No
    NUM_VERTICAL_TILES_ATTRIBUTE = _num_tile_rows
    SEED_COLUMN = 0
    RASTER_INDEX_ATTRIBUTE = _raster_index
    NUM_HORIZONTAL_TILES_ATTRIBUTE = _num_tile_columns
    TILES -> TileName_3
TileName_3: StringConcatenator
    ACTION = Create New Attribute
    VAL_ATTR = _tile_name
    PARM_LINE = @Value(fme_basename)_@Value(_tile_column)_@Value(_tile_row)
    -> TIFF (writer PNGRASTER_4)
TIFF (writer PNGRASTER_4)
