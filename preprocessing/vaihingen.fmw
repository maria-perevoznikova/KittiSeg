FME workspace vaihingen.fmw

Parameters:
- SourceDataset_TIFF = ""C:\Projects\VP2\ISPRS_semantic_labeling_Vaihingen\top\*.tif" "C:\Projects\VP2\ISPRS_semantic_labeling_Vaihingen\top\*.tiff" "C:\Projects\VP2\ISPRS_semantic_labeling_Vaihingen\top\*.itiff" "C:\Projects\VP2\ISPRS_semantic_labeling_Vaihingen\top\*.ovr""   # Source TIFF (Tagged Image File Format) File(s)
- DestDataset_PNGRASTER = C:\Projects\VP2\ISPRS_semantic_labeling_Vaihingen\top_tiles   # Destination PNG (Portable Network Graphics) Folder
- SourceDataset_TIFF_3 = ""C:\Projects\VP2\ISPRS_semantic_labeling_Vaihingen\gts_for_participants\*.tif" "C:\Projects\VP2\ISPRS_semantic_labeling_Vaihingen\gts_for_participants\*.tiff" "C:\Projects\VP2\ISPRS_semantic_labeling_Vaihingen\gts_for_participants\*.itiff" "C:\Projects\VP2\ISPRS_semantic_labeling_Vaihingen\gts_for_participants\*.ovr""   # Source TIFF (Tagged Image File Format) File(s)
- DestDataset_PNGRASTER_3 = C:\Projects\VP2\ISPRS_semantic_labeling_Vaihingen\gts_tiles   # Destination PNG (Portable Network Graphics) Folder

Readers:
- TIFF_1: TIFF from $(SourceDataset_TIFF)
- TIFF_2: TIFF from $(SourceDataset_TIFF_3)

Writers:
- PNGRASTER_1: PNGRASTER to $(DestDataset_PNGRASTER)
- PNGRASTER_2: PNGRASTER to $(DestDataset_PNGRASTER_3)

Note: OrthoPhotos
TIFF (reader TIFF_1)
    -> RasterProperties
RasterProperties: RasterPropertyExtractor
    -> ClipSize
ClipSize: AttributeCreator
    ATTR_LIST = _tile_num_rows,768,_tile_num_columns,624,_clip_rows,@Evaluate(@Value(_num_rows)-@Value(_num_rows)%768),_clip_columns,@Evaluate(@Value(_num_columns)-@Value(_num_columns)%624)
    -> RasterClipper
    -> Inspector
RasterClipper: RasterSubsetter
    NUM_ROWS = @Value(_clip_rows)
    NUM_LEFT_PADDDING_COLUMNS = 0
    NUM_TOP_PADDING_ROWS = 0
    NUM_BOTTOM_PADDING_ROWS = 0
    NUM_RIGHT_PADDDING_COLUMNS = 0
    START_COLUMN = 0
    NUM_COLUMNS = @Value(_clip_columns)
    START_ROW = 0
    -> RasterTiler
RasterTiler
    NUM_HORIZONTAL_TILES_ATTRIBUTE = _num_tile_columns
    FORCE_EQUAL_SIZED_TILES = No
    NUM_VERTICAL_TILES_ATTRIBUTE = _num_tile_rows
    SEED_COLUMN = 0
    SEED_ROW = 0
    TILE_COLUMN_ATTRIBUTE = _tile_column
    TILE_ROW_ATTRIBUTE = _tile_row
    TILESIZE_OR_NUMTILES = Tile Size
    NUM_TILE_ROWS = @Value(_tile_num_rows)
    NUM_TILE_COLUMNS = @Value(_tile_num_columns)
    RASTER_INDEX_ATTRIBUTE = _raster_index
    TILES -> TileName
TileName: StringConcatenator
    ACTION = Create New Attribute
    PARM_LINE = @Value(fme_basename)_@Value(_tile_column)_@Value(_tile_row)
    VAL_ATTR = _tile_name
    -> Raster1 (writer PNGRASTER_1)
Raster1 (writer PNGRASTER_1)
Inspector [off]
Note: GroundTruth
TIFF (reader TIFF_2)
    -> RasterProperties_2
RasterProperties_2: RasterPropertyExtractor
    -> ClipSize_2
ClipSize_2: AttributeCreator
    ATTR_LIST = _tile_num_rows,768,_tile_num_columns,624,_clip_rows,@Evaluate(@Value(_num_rows)-@Value(_num_rows)%768),_clip_columns,@Evaluate(@Value(_num_columns)-@Value(_num_columns)%624)
    -> RasterClipper_2
RasterClipper_2: RasterSubsetter
    NUM_ROWS = @Value(_clip_rows)
    NUM_LEFT_PADDDING_COLUMNS = 0
    NUM_TOP_PADDING_ROWS = 0
    NUM_BOTTOM_PADDING_ROWS = 0
    NUM_RIGHT_PADDDING_COLUMNS = 0
    START_COLUMN = 0
    NUM_COLUMNS = @Value(_clip_columns)
    START_ROW = 0
    -> RasterTiler_2
RasterTiler_2
    NUM_HORIZONTAL_TILES_ATTRIBUTE = _num_tile_columns
    FORCE_EQUAL_SIZED_TILES = No
    NUM_VERTICAL_TILES_ATTRIBUTE = _num_tile_rows
    SEED_COLUMN = 0
    SEED_ROW = 0
    TILE_COLUMN_ATTRIBUTE = _tile_column
    TILE_ROW_ATTRIBUTE = _tile_row
    TILESIZE_OR_NUMTILES = Tile Size
    NUM_TILE_ROWS = @Value(_tile_num_rows)
    NUM_TILE_COLUMNS = @Value(_tile_num_columns)
    RASTER_INDEX_ATTRIBUTE = _raster_index
    TILES -> TileName_2
TileName_2: StringConcatenator
    ACTION = Create New Attribute
    PARM_LINE = @Value(fme_basename)_@Value(_tile_column)_@Value(_tile_row)
    VAL_ATTR = _tile_name
    -> Raster1 (writer PNGRASTER_2)
Raster1 (writer PNGRASTER_2)
